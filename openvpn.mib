OPENVPN-MIB DEFINITIONS ::= BEGIN

IMPORTS
	OBJECT-TYPE, MODULE-IDENTITY, experimental, 
	Unsigned32, Integer32
		FROM SNMPv2-SMI
	DisplayString
		FROM SNMPv2-TC;

openvpnMib MODULE-IDENTITY
	LAST-UPDATED "202107070000Z"
	ORGANIZATION 
		"Open Source Project"
	CONTACT-INFO 
		"Philipp Helo Rehs
		http://github.com/Phhere/openvpn-snmp"
	DESCRIPTION 
		"A simple mib for openvpn servers"
	REVISION     "202107070000Z"
	DESCRIPTION 
		"Initial Version"
::= { experimental 1991 }

openvpn              OBJECT IDENTIFIER ::= { openvpnMib 1 }

openvpnServerTableLength  OBJECT-TYPE
	SYNTAX     Unsigned32
	MAX-ACCESS read-only
	STATUS     current
	DESCRIPTION 
		"Count of running VPN-Server tasks"
	::= { openvpn 1 }

openvpnServerTable  OBJECT-TYPE
	SYNTAX SEQUENCE OF OpenvpnServerEntry
	MAX-ACCESS not-accessible
	STATUS     current
	DESCRIPTION 
		"List of running VPN-Server task"
	::= { openvpn 2 }

openvpnServerEntry  OBJECT-TYPE
	SYNTAX 	OpenvpnServerEntry
	MAX-ACCESS not-accessible
	STATUS     current
	DESCRIPTION 
		"VPN server entry"
	INDEX { openvpnServerID }
	::= { openvpnServerTable 1 }

OpenvpnServerEntry ::= SEQUENCE {
	openvpnServerID
		Integer32,
	openvpnServerName
		DisplayString,
	openvpnServerUsers
		Unsigned32,
	openvpnServerTrafficSend
		Unsigned32,
	openvpnServerTrafficReceived
		Unsigned32
}

openvpnServerID  OBJECT-TYPE
	SYNTAX     Integer32
	MAX-ACCESS read-only
	STATUS     current
	DESCRIPTION 
		"VPN server index number"
	::= { openvpnServerEntry 1 }

openvpnServerName  OBJECT-TYPE
	SYNTAX     DisplayString
	MAX-ACCESS read-only
	STATUS     current
	DESCRIPTION 
		"VPN Server name"
	::= { openvpnServerEntry 2 }

openvpnServerUsers  OBJECT-TYPE
	SYNTAX     Unsigned32
	MAX-ACCESS read-only
	STATUS     current
	DESCRIPTION 
		"VPN server total connected users"
	::= { openvpnServerEntry 3 }

openvpnServerTrafficSend  OBJECT-TYPE
	SYNTAX     Counter32
	MAX-ACCESS read-only
	STATUS     current
	DESCRIPTION 
		"VPN server traffic send"
	::= { openvpnServerEntry 4 }

openvpnServerTrafficReceived  OBJECT-TYPE
	SYNTAX     Counter32
	MAX-ACCESS read-only
	STATUS     current
	DESCRIPTION 
		"VPN server traffic received"
	::= { openvpnServerEntry 5 }

openvpnUserTableLength  OBJECT-TYPE
	SYNTAX     Unsigned32
	MAX-ACCESS read-only
	STATUS     current
	DESCRIPTION 
		"VPN entries in table of connected users"
	::= { openvpn 3 }

openvpnUserTable  OBJECT-TYPE
	SYNTAX SEQUENCE OF OpenvpnUserEntry
	MAX-ACCESS not-accessible
	STATUS     current
	DESCRIPTION 
		"VPN table of connected users"
	::= { openvpn 4 }

openvpnUserEntry  OBJECT-TYPE
	SYNTAX 	OpenvpnUserEntry
	MAX-ACCESS not-accessible
	STATUS     current
	DESCRIPTION 
		"VPN user entry"
	INDEX { openvpnUserName }
	::= { openvpnUserTable 1 }

OpenvpnUserEntry ::= SEQUENCE {
	openvpnUserID
		Integer32,
	openvpnUserName
		DisplayString,
	openvpnUserServer
		DisplayString,
	openvpnUserTrafficSend
		Counter32,
	openvpnUserTrafficReceived
		Counter32,
	openvpnUserConnecttime
		DisplayString
}

openvpnUserID  OBJECT-TYPE
	SYNTAX     Integer32
	MAX-ACCESS read-only
	STATUS     current
	DESCRIPTION 
		"VPN user index number"
	::= { openvpnUserEntry 1 }

openvpnUserName  OBJECT-TYPE
	SYNTAX     DisplayString
	MAX-ACCESS read-only
	STATUS     current
	DESCRIPTION 
		"VPN user client name"
	::= { openvpnUserEntry 2 }

openvpnUserServer  OBJECT-TYPE
	SYNTAX     DisplayString
	MAX-ACCESS read-only
	STATUS     current
	DESCRIPTION 
		"VPN server name"
	::= { openvpnUserEntry 3 }

openvpnUserTrafficSend  OBJECT-TYPE
	SYNTAX     Counter32
	MAX-ACCESS read-only
	STATUS     current
	DESCRIPTION 
		"VPN user traffic send"
	::= { openvpnUserEntry 4 }

openvpnUserTrafficReceived  OBJECT-TYPE
	SYNTAX     Counter32
	MAX-ACCESS read-only
	STATUS     current
	DESCRIPTION 
		"VPN user traffic received"
	::= { openvpnUserEntry 5 }

openvpnUserConnecttime  OBJECT-TYPE
	SYNTAX     DisplayString
	MAX-ACCESS read-only
	STATUS     current
	DESCRIPTION 
		"VPN user client connected time stamp"
	::= { openvpnUserEntry 6 }

END
